(defun c:addsymbol (/ dcl_id SS X TXT LST NTXT)
    (setq U:G "(command \"undo\" \"group\")")
   (setq U:E "(command \"undo\" \"en\")")
   (read U:G)
   (read U:E)
    (if (= s1 nil)
      (setq s1 "(")
   )
   (if (= s2 nil)
      (setq s2 ")")
   )
   (setq cnt 1)
   (setq dcl_id (load_dialog "addsymbol.dcl"))  
      (if (null (new_dialog "addsymbol" dcl_id))
         (exit)
      )
      (set_tile "s1" s1)
      (action_tile "s1" "(setq s1 $value)")
      (set_tile "s2" s2)
      (action_tile "s2" "(setq s2 $value)")      
      (action_tile "pick" "(done_dialog 4)")
      (setq what_next (start_dialog))
      (cond
         ((= what_next 4)
          (while (null (setq SS (ssget (list (cons 0 "TEXT")))))
             (princ "\nNo Text Found ")
             (princ)
          )
         )
         ((= what_next 0) (prompt "\nuser cancelled dialog"))
      )
      (setq X 0)
   (progn
      (while (setq TXT (ssname SS X))
         (setq LST (entget TXT))
         (setq NTXT (strcat s1 (cdr (assoc 1 LST)) s2))
         (setq LST (subst (cons 1 NTXT) (assoc 1 LST) LST))
         (entmod LST)
         (setq X (1+ X))
      )
   )      
   (start_dialog)
   (unload_dialog dcl_id)
   (princ)
)
