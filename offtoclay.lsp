(defun c:offtoclay ()
    (defun dxf (code elist) (cdr (assoc code (entget elist))))
    (setq cd (getvar "offsetdist")
          oc (getvar "cmdecho")
    )
    (setvar "cmdecho" 0)
    (if (= -1 cd)
        (setq cd 0)
    )
    (setq text (strcat "\nEnter offset distance <" (rtos cd) "> "))
    (princ text)
    (setq od (getdist))
    (if (= nil od)
        (setq od cd)
    )
   (setq x 0)
   (while (< x 10000)
    (setq obj  (car (entsel "\nSelect object to offset: "))
          pt   (getpoint "\nSelect side to offset: ")
          la   (dxf 8 obj)
          clay (getvar "clayer")
    )
    (command "_offset" od obj pt "")
    (setq ed (entget (entlast))
          ed (subst (cons 8 clay) (assoc 8 ed) ed)
    )
    (entmod ed)
      (setq x (1+ x))
      )
    (setvar "cmdecho" oc)
    (princ)
)
