(defun c:offsetcurb ()
   (if (= 1d nil)
      (setq 1d 0)
      (setq def1 1d)
   )
   (if (= 2d nil)
      (setq 2d 0)
      (setq def2 2d)
   )
   (if (= 3d nil)
      (setq 3d 0)
      (setq def3 3d)
   )
   (setq oc (getvar "cmdecho")
         t1 (strcat "\nEnter the first offset distance: <" (rtos 1d) "> ")
         t2 (strcat "\nEnter the second offset distance: <" (rtos 2d) "> ")
         t3 (strcat "\nEnter the third offset distance or 0 for none: <" (rtos 3d) "> ")
   )
   (princ t1)
   (setq 1d (getdist))
   (princ t2)
   (setq 2d (getdist))
   (princ t3)
   (setq 3d (getreal))
   (if (= nil 1d)
      (setq 1d def1)
   )
   (if (= nil 2d)
      (setq 2d def2)
   )
   (if (= nil 3d)
      (setq 3d def3)
   )
   (while (setq obj (car (entsel "\nSelect object to offset: "))
                pt  (getpoint "\nSelect side to offset: ")
          )
      (setvar "cmdecho" 0)
      (command "_offset" 1d obj pt "")
      (setq ed1 (entget (entlast))
            ed  (subst (cons 8 curbla) (assoc 8 ed1) ed1)
      )
      (command "_offset" 2d obj pt "")
      (setq ed2 (entget (entlast))
            ed  (subst (cons 8 curbla) (assoc 8 ed2) ed2)
      )
      (if (/= 3d 0.0)
         (command "_offset" 3d obj pt "")
      )
      (setq ed3 (entget (entlast))
            ed  (subst (cons 8 curbla) (assoc 8 ed3) ed3)
      )
      (setvar "cmdecho" oc)
   )
   (princ)
)
