(defun
     c:styles (/ dcl_id)
    (setq dcl_id (load_dialog "styles.dcl"))
    (if (not (new_dialog "STYLES" dcl_id))
        (exit)
    )
    (setq ofil (open "c:/my documents/cad/mylisp/asdf.dat" "r"))
    (setq ala (read-line ofil))
    (setq ats (read-line ofil))
    (setq atsty (read-line ofil))
    (setq lts (read-line ofil))
    (setq ltsty (read-line ofil))
    (setq tol (read-line ofil))
    (setq lots (read-line ofil))
    (setq lotstyle (read-line ofil))
    (setq lol (read-line ofil))
    (setq curbla (read-line ofil))
    (setq offla (read-line ofil))
    (close ofil)
    (set_tile "ala" ala)
    (set_tile "ats" ats)
    (set_tile "atsty" atsty)
    (set_tile "lts" lts)
    (set_tile "ltsty" ltsty)
    (set_tile "tol" tol)
    (set_tile "lots" lots)
    (set_tile "lotstyle" lotstyle)
    (set_tile "lol" lol)
    (set_tile "curbla" curbla)
    (set_tile "offla" offla)
    (set_tile "lotstyle" lotstyle)
    (action_tile "ala" "(setq ala $value)")
    (action_tile "ats" "(setq ats $value)")
    (action_tile "atsty" "(setq atsty $value)")
    (action_tile "lts" "(setq lts $value)")
    (action_tile "ltsty" "(setq ltsty $value)")
    (action_tile "tol" "(setq tol $value)")
    (action_tile "lots" "(setq lots $value)")
    (action_tile "lotsty" "(setq lotsty $value)")
    (action_tile "lol" "(setq lol $value)")
    (action_tile "curbla" "(setq curbla $value)")
    (action_tile "offla" "(setq offla $value)")
    (action_tile "lotstyle" "(setq lotstyle $value)")
    (start_dialog)
    (unload_dialog dcl_id)
    (unload_dialog dcl_id)
    (setq varlist (list ala ats atsty lts ltsty tol lots lotstyle lol curbla offla))
    (setq ofil (open "c:/my documents/cad/mylisp/asdf.dat" "w"))
    (foreach itm varlist (write-line itm ofil))
    (close ofil)
    (princ)
)
