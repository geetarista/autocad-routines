(defun c:tick (/ tm bm lc cr ap kp tl qe ed cp rd sa ea sp ep d1 d2 s1 s2 e1 e2 qm)
   (setvar "CmdEcho" 0)
   (setq tm 0)
   (setq
      bm (getvar "BlipMode")
      lc (getvar "LimCheck")
      os (getvar "osmode")
   )
   (setvar "BlipMode" 0)
   (setvar "LimCheck" 0)
   (setvar "osmode" 0)
   (setq cr (* (getvar "ViewSize") 0.025))
   (setq ap "\nSelect arc for tick placement: ")
   (setq tl (getdist "\nEnter tick length: "))
   (if (and tl (> tl 0))
      (progn
	 (while	(setq qe (entsel ap))
	    (setq ed (entget (car qe)))
	    (if tl
	       (progn
		  (setq
		     cp	(cdr (assoc 10 ed))
		     rd	(cdr (assoc 40 ed))
		     sa	(cdr (assoc 50 ed))
		     ea	(cdr (assoc 51 ed))
		     sp	(polar cp sa rd)
		     ep	(polar cp ea rd)
		     d1	(- rd (/ tl 2.0))
		     d2	(+ rd (/ tl 2.0))
		     s1	(polar cp sa d1)
		     s2	(polar cp sa d2)
		     e1	(polar cp ea d1)
		     e2	(polar cp ea d2)
		  )
		  (command ".Line" s1 s2 "")
		  (setq tm (1+ tm))
		  (command ".Line" e1 e2 "")
		  (setq tm (1+ tm))
		  (redraw)
	       )
	    )
	 )
      )
   )
   (setvar "BlipMode" bm)
   (setvar "LimCheck" lc)
   (setvar "CmdEcho" 1)
   (setvar "osmode" os)
   (redraw)
   (princ)
)
