(defun c:text2mtext (/	mwid  dset  ibrk  bitm	bent  sset  rect  mlay	mcol  mlst  bins
		  bang	tang  nins  num	  ndis	chnd  cent  nhnd  nstr	str   p1    p2
		  p3	dis   dvx   dvy	  dvz	new
		 )
   (defun col2str (inp)
      (cond
	 ((= inp nil) (setq ret "BYLAYER"))
	 ((= inp 256) (setq ret "BYLAYER"))
	 ((= inp 0) (setq ret "BYBLOCK"))
	 ((and (> inp 0) (< inp 255)) (setq ret (itoa inp)))
	 (t nil)
      )
   )
   (defun textrect (tent / ang sro cro t1 t2 p1 p2 p3 p4)
      (setq
	 p0  (cdr (assoc 10 tent))
	 ang (cdr (assoc 50 tent))
	 sro (sin ang)
	 cro (cos ang)
	 t1  (car (textbox tent))
	 t2  (cadr (textbox tent))
	 p1  (list
		(+ (car p0) (- (* (car t1) cro) (* (cadr t1) sro)))
		(+ (cadr p0) (+ (* (car t1) sro) (* (cadr t1) cro)))
	     )
	 p2  (list
		(+ (car p0) (- (* (car t2) cro) (* (cadr t1) sro)))
		(+ (cadr p0) (+ (* (car t2) sro) (* (cadr t1) cro)))
	     )
	 p3  (list
		(+ (car p0) (- (* (car t2) cro) (* (cadr t2) sro)))
		(+ (cadr p0) (+ (* (car t2) sro) (* (cadr t2) cro)))
	     )
	 p4  (list
		(+ (car p0) (- (* (car t1) cro) (* (cadr t2) sro)))
		(+ (cadr p0) (+ (* (car t1) sro) (* (cadr t2) cro)))
	     )
      )
      (list p1 p2 p3 p4)
   )
   (setq cmd (getvar "CMDECHO"))
   (setvar "CMDECHO" 0)
   (command "_.UNDO" "_G")
   (setq mwid 0.0)
   (setq dset (ssadd))
   (setq bitm (car (entsel "\nPick text in order: ")))
   (setq bent (entget bitm))
   (setq rect (textrect bent))
   (setq chk (distance (car rect) (cadr rect)))
   (if (> chk mwid)
      (setq mwid chk)
   )
   (if (= "TEXT" (cdr (assoc 0 bent)))
      (progn
	 (redraw bitm 3)
	 (setq sset (ssget '((0 . "TEXT"))))
	 (if sset
	    (progn
	       (setq rect (textrect bent))
	       (setq orig rect)
	       (setq mlay (cdr (assoc 8 bent)))
	       (setq mcol (cdr (assoc 62 bent)))
	       (setq mlst (list (cdr (assoc 1 bent))))
	       (if (> (cdr (assoc 72 bent)) 0)
		  (setq bins (cdr (assoc 11 bent)))
		  (setq bins (cdr (assoc 10 bent)))
	       )
	       (setq bang (cdr (assoc 50 bent)))
	       (setq tang (- bang (/ PI 2)))
	       (setq nins bins)
	       (ssdel bitm sset)
	       (while (> (sslength sset) 0)
		  (setq
		     num (sslength sset)
		     itm 0
		  )
		  (setq ndis 99999999.9)
		  (while (< itm num)
		     (setq chnd (ssname sset itm))
		     (setq cent (entget chnd))
		     (if (> (cdr (assoc 72 cent)) 0)
			(setq cins (cdr (assoc 11 cent)))
			(setq cins (cdr (assoc 10 cent)))
		     )
		     (setq cdis (distance bins cins))
		     (if (< cdis ndis)
			(setq
			   ndis	cdis
			   nhnd	chnd
			   nent	cent
			)
		     )
		     (setq itm (1+ itm))
		  )
		  (setq dset (ssadd nhnd dset))
		  (ssdel nhnd sset)
		  (setq rect (textrect nent))
		  (setq chk (distance (car rect) (cadr rect)))
		  (if (> chk mwid)
		     (setq mwid chk)
		  )
		  (setq nstr (cdr (assoc 1 nent)))
		  (setq mlst (append mlst (list nstr)))
	       )
	       (entdel bitm)
	       (setq
		  num (sslength dset)
		  itm 0
	       )
	       (while (< itm num)
		  (setq hnd (ssname dset itm))
		  (entdel hnd)
		  (setq itm (1+ itm))
	       )
	       (setq cla (getvar "CLAYER"))
	       (setq cec (getvar "CECOLOR"))
	       (setvar "CECOLOR" "BYLAYER")
	       (setq celt (getvar "CELTYPE"))
	       (setvar "CELTYPE" "BYLAYER")
	       (setq thk (getvar "THICKNESS"))
	       (setvar "THICKNESS" 0)
	       (if (>= (atoi (getvar "ACADVER")) 13)
		  (progn (setq celts (getvar "CELTSCALE")) (setvar "CELTSCALE" 1.0))
	       )
	       (setvar "CLAYER" mlay)
	       (if (/= mcol nil)
		  (setvar "CECOLOR" (col2str mcol))
	       )
	       (setq mwid (+ mwid (* mwid 0.025)))
	       (setq p1 (car orig))
	       (setq p2 (cadr orig))
	       (setq dis (distance p1 p2))
	       (setq dvx (/ (- (car p2) (car p1)) dis))
	       (setq dvy (/ (- (cadr p2) (cadr p1)) dis))
	       (setq p3 (list dvx dvy 0.0))
	       (setq
		  nins
		    (list
		       (car (cadddr orig))
		       (cadr (cadddr orig))
		       (nth 2 (cdr (assoc 10 bent)))
		    )
	       )
	       (setq new '((0 . "MTEXT") (100 . "AcDbEntity") (100 . "AcDbMText")))
	       (setq new (append new (list (assoc 7 bent))))
	       (setq new (append new (list (assoc 8 bent))))
	       (setq new (append new (list (cons 10 nins))))
	       (setq new (append new (list (cons 11 p3))))
	       (foreach
		   lin mlst
		  (setq lin (strcat lin "\\P"))
		  (setq new (append new (list (cons 1 lin))))
	       )
	       (setq new (append new (list (assoc 40 bent))))
	       (setq new (append new (list (cons 41 mwid))))
	       (setq new (append new (list (cons 71 1))))
	       (setq new (append new (list (cons 72 1))))
	       (entmake new)
	       (if (>= (atoi (getvar "ACADVER")) 13)
		  (setvar "CELTSCALE" celts)
	       )
	       (setvar "THICKNESS" thk)
	       (setvar "CELTYPE" celt)
	       (setvar "CECOLOR" cec)
	       (setvar "CLAYER" cla)
	       (setq sset nil)
	       (setq dset nil)
	       (setq lst nil)
	       (command "_.UNDO" "_E")
	       (setvar "CMDECHO" cmd)
	    )
	 )
      )
   )
   (setq sset nil)
   (setq mlst nil)
   (princ)
)
